/*
 * $Id: //DukePro/eagle/ulp/origins.ulp#4 $
 * $DateTime: 2011/07/23 09:51:45 $
 * Modified for EagleV6. Warren Brayshaw 17/11/2012
 *
 * This will emit a list of parts with SMD pads and their origins.
 */
#usage "Produces a CSV list of parts with SMD pads, their orgins,"
" and whether each is placed on the top of the board or the bottom."
" Units of output = mils."

string partName[], partPackage[], partValue[];
real	partX[], partY[], partA[];
int		partMirror[];
int		numParts = 0;
real	xExtent = 0.0;
real	yExtent = 0.0;

void CollectPartData(void) {
	board(B) {
		int	xExtentInt = 0;
		int	yExtentInt = 0;

		/*
		 * Look for the wires in the Dimension layer.  Identify the largest
		 * X value.
		 */
		B.wires(W) {
			if (W.layer == 20) {
				if (W.x1 > xExtentInt)
					xExtentInt = W.x1;
				if (W.x2 > xExtentInt)
					xExtentInt = W.x2;
				if (W.y1 > yExtentInt)
					yExtentInt = W.y1;
				if (W.y2 > yExtentInt)
					yExtentInt = W.y2;
			}
		}

		// Convert from tenths of micrometers to mils
		//xExtent = xExtentInt / 10.0 / 25.4;
		//yExtent = yExtentInt / 10.0 / 25.4;
		xExtent = u2mm(xExtentInt);
		yExtent = u2mm(yExtentInt);

		B.elements(E) {
			int isSMD = 0;

			isSMD = 0;
			E.package.contacts(C) {
				if (C.smd) {
					isSMD = 1;
					break;
				}
			}
			if (isSMD != 0) {
				//real xr, yr;
				//xr = E.x / 10;	// x coord in micrometers
				//yr = E.y / 10;

				partName[numParts] = E.name;
				partMirror[numParts] = E.mirror;
				partPackage[numParts] = E.package.name;
				partValue[numParts] = E.value;
				//partX[numParts] = xr/25.4;
				//partY[numParts] = yr/25.4;
				partX[numParts] = u2mm(E.x);
				partY[numParts] = u2mm(E.y);

//角度问题, 原本是大于180就减360变成负角度
                		partA[numParts] = E.angle;
				//if (E.angle > 180)
				//	partA[numParts] = E.angle-360;
				//else
				//	partA[numParts] = E.angle;

				++numParts;
			}
		}
	}
}

string listLines[];
void GenListLines(void) {
	for (int i = 0; i < numParts; ++i) {
		sprintf(listLines[i], "%s\t%s\t%.1f\t%.1f\t%.1f\t%s",
			partMirror[i] ?  "B" : "T",
			partName[i],
			partX[i], partY[i], partA[i],
			partPackage[i]);
	}
}

void SaveList(void) {
	string fileName;
	string assyName;
	board(BRD) {
        string assyAttr;
        string revAttr;

        BRD.attributes(ATTR) {
            if (ATTR.name == "REVISION")
                revAttr = ATTR.value;
            if (ATTR.name == "ASSEMBLY")
                assyAttr = ATTR.value;
        }

        string pn;
        pn = filesetext(filename(BRD.name), "");
        int dashIndex;
        dashIndex = strchr(pn, '-');
        if (dashIndex >= 0) {
            pn = strsub(pn, 0, dashIndex);
        }

        fileName = filedir(BRD.name) + pn;

        if (assyAttr != "") {
            fileName += "-" + assyAttr;
        }
        if (revAttr != "") {
            fileName += "-Rev" + revAttr;
        }
        assyName = filename(fileName);
        fileName += "-smt.csv";
    }
	fileName = dlgFileSave("储存零件座标档", fileName, "*.csv");
	if (fileName) {
		string a[];
		if (!fileglob(a, fileName) || dlgMessageBox(fileName + " 已存在\n\n覆写?", "&Yes", "-&No") == 0) {
			output(fileName, "wt") {

				//printf("%s\n", assyName);
				//printf("Extents,%.1f,%.1f\n", xExtent, yExtent);
printf("\"Designator\",\"Footprint\",\"Mid X\",\"Mid Y\",\"Ref X\",\"Ref Y\",\"Pad X\",\"Pad Y\",\"Layer\",\"Rotation\",\"Comment\"\n");
printf("\"\"\n");

//"JP1","SIP2","63.5mm","124.714mm","63.5mm","125.984mm","63.5mm","125.984mm","T","270.00","GND_SEL"


				for (int i = 0; i < numParts; ++i) {
					printf("\"%s\",\"%s\",\"%.1fmm\",\"%.1fmm\",\"%.1fmm\",\"%.1fmm\",\"%.1fmm\",\"%.1fmm\",\"%s\",\"%.1f\",\"%s\"\n",
partName[i],partPackage[i],partX[i], partY[i],partX[i], partY[i],partX[i], partY[i],partMirror[i] ?  "B" : "T",partA[i],partValue[i]);
						//partMirror[i] ?  "B" : "T",
						//partName[i],
						//partX[i], partY[i], partA[i],
						//partPackage[i]);
				}
			}
		}
	}
}

CollectPartData();
GenListLines();

int selected = 0;
dlgDialog("Part Origins") {
	string buf;
	dlgLabel("仅列出 SMD 元件");
	dlgLabel("单位 \"mm\"");
	dlgListView("上层T/下层B\t零件名称\tX\tY\t角度\t封装", listLines, selected);
    dlgHBoxLayout {
		dlgVBoxLayout {
			sprintf(buf, "X 范围: %.1f mm", xExtent);
			dlgLabel(buf);
			sprintf(buf, "Y 范围: %.1f mm", yExtent);
			dlgLabel(buf);

			//dlgLabel("Extents");
			//sprintf(buf, "(%.1f %.1f)", xExtent, yExtent);
			//dlgLabel(buf);
		}
        dlgStretch(1);
        dlgPushButton("&S.储存...") SaveList();
        dlgPushButton("&C.关闭") dlgAccept();
    }
};


/* vim: set ts=4 sw=4 et ai: */
